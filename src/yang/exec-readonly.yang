module exec-readonly {

  namespace "http://example.com/exec-readonly";
  prefix exec-readonly;

  import ietf-inet-types {
    prefix inet;
  }
  import tailf-common {
    prefix tailf;
  }
  import tailf-ncs {
    prefix ncs;
  }

  description
    "Bla bla...";

  revision 2016-01-01 {
    description
      "Initial revision.";
  }

  augment /ncs:devices/ncs:device {
    tailf:action exec-readonly {
      tailf:info "execute read-only commands. Allowed commands are ping, show and display";
      tailf:actionpoint exec-readonly-action;
      input {
        leaf command {
          type string;
        }
      }
      output {
        leaf result {
          type string;
        }
      }
    }
  }
  list exec-readonly {
    description "This is an RFS skeleton service";

    key name;
    leaf name {
      tailf:info "Unique service id";
      tailf:cli-allow-range;
      type string;
    }

    uses ncs:service-data;
    ncs:servicepoint exec-readonly-servicepoint;

    // may replace this with other ways of refering to the devices.
    leaf-list device {
      type leafref {
        path "/ncs:devices/ncs:device/ncs:name";
      }
    }

    // replace with your own stuff here
    leaf dummy {
      type inet:ipv4-address;
    }
  }
}
